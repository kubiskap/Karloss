CALMllsap {iso(1) standard(0) calm-ll-sap(21218) version1(1)} DEFINITIONS AUTOMATIC TAGS::=BEGIN


-- EXPORTS;

IMPORTS 

ITS-scuId FROM CALMmanagement { iso (1) standard (0) calm-management (24102) local (1) version1 (1)}


ErrStatus FROM CALMmsap { iso (1) standard (0) calm-management (24102) msap (3) version1 (1)}


MediumCost FROM CITSapplReq {iso(1) standard(0) cits-applReq (17423) version1 (1)} 

LogicalChannelType FROM CITSapplMgmtComm {iso(1) standard(0) cits-applMgmt (17419) comm (3) version1 (1)}
;

-- End of IMPORTS

Alt::=INTEGER(0..65535) -- Resolution 0,1 m.

CIaClass::=INTEGER{
	unknown	(0),
	ciac-1	(1),
	ciac-3	(2),
	ciac-2	(3)
	} (0..255)

CIclass::=INTEGER{
	unknown	(0),
	cic-wl1	(1),
	cic-wl2	(2),
	cic-wl3	(3),
	cic-wl4	(4),
	cic-wl5	(5),
	cic-lan1	(254),
	cic-lan2	(255)
	} (0..255)

Link-ID::=SEQUENCE{	-- Link-ID
	remoteCIID	EUI64,	-- CI in peer ITS-S(s)
	localCIID	EUI64	-- Unique ID of local CI
	}

CIstatus::=INTEGER{
	not-existent	(0),
	existent	(1),
	unknown	(2),
	registered	(4),
	active	(8),
	connected	(16),
	suspended	(64),
	inactive	(128)
	} (0..255)

CommProfile::=SEQUENCE (SIZE(0..255)) OF I-Param

Connect::=INTEGER{
	automatic	(0),
	manual	(255)
	} (0..255)

IN-SAPaddress::=INTEGER(0..255)

DataRate::= INTEGER(0..4294967295)	-- in 100 bit/s

DataRatesNW::=SEQUENCE{	-- available to the appl.
	minimum	DataRate,	-- minimum possible value
	maximum	DataRate	-- maximum possible value
	}

Directivity::=SEQUENCE{
	mode	DirMode,
	dirPredef	INTEGER(0..255),	-- 0: see dirVar
			-- >0: predefined direction
	fill	BIT STRING (SIZE(7)),
	dirVar	SEQUENCE (SIZE(0..1)) OF CHOICE{dirVar DirVar}
	}

DirMode::=INTEGER{
	fixed	(0),
	tracking	(255)
	} (0..255)


DirVar::=SEQUENCE{
	bsAzimuth	INTEGER(-256..255) ,	-- -180 - +180
	bsElevation	INTEGER(-128..127) ,	-- -90 - +90
	openHorizontal	INTEGER(0..255) ,	-- 0 - 180
	openVertical	INTEGER(0..255)	-- 0 - 180
	}

Dut::=SEQUENCE{
	year	INTEGER(0..255),	-- year - 2000
	month	INTEGER(0..255),	-- 1 .. 12
	day	INTEGER(0..255),	-- 1 .. 31
	hour	INTEGER(0..255),	-- 0 .. 23
	minute	INTEGER(0..255),	-- 0 .. 59
	second	INTEGER(0..255),	-- 0 .. 59
	fractSec	INTEGER(0..255)	-- 3,90625 ms resolution
	}

TxPowMax::=INTEGER(0..255) -- unit, minimum value and step size defined by access technology (medium)

Errors::=SEQUENCE (SIZE(0..255)) OF SingleError

SingleError::=SEQUENCE{
	paramNo	INTEGER(0..255), -- ref number of parameter
	fill	BIT STRING (SIZE(7)), -- to be filled with '0's
	med	SEQUENCE (SIZE(0..1)) OF CHOICE{medPar MedPar}, -- only for medium-specific parameters
	errStatus	ErrStatus	-- IS24102-3
	}

Gs::=INTEGER(0..65535) -- Resolution 0,01 m/s.

KineVectIn::=SEQUENCE{
	dut	Dut, -- date and universal time
	lat	Lat, -- latitude
	lon	Lon, -- longitude
	alt	Alt, -- altitude
	gs	Gs, -- ground speed
	tta	Tta -- true track angle
	}

KineVectOut::=SEQUENCE{
	dut	Dut, -- date and universal time
	fill	BIT STRING (SIZE(5)), -- used for octet alignment in PER
	options	SEQUENCE (SIZE(0..5)) OF KineVectOptions -- options
	}

KineVectOptions::=CHOICE{
	lat	Lat, -- latitude
	lon	Lon, -- longitude
	alt	Alt, -- altitude
	gs	Gs, -- ground speed
	tta	Tta -- true track angle
	}

Lat::=INTEGER(-2147483648..2147483647) -- equals ± ?/2

Lon::=INTEGER(-2147483648..2147483647) -- equals ± ?

LLserviceAddr::=SEQUENCE{  
	csap	IN-SAPaddress,
	linkID	Link-ID
	}

MedPar::=SEQUENCE{
	medium	MedType,
	no	INTEGER(0..255)
	}

MediumParam::=SEQUENCE{
	mediumPar	MedPar,
	detail	OCTET STRING (SIZE(0..65535)) -- details defined
	}		-- in medium standard

MACaddress::=OCTET STRING (SIZE(6))

MediumUsage::=SEQUENCE{
	receive	INTEGER(0..255),
	transmit	INTEGER(0..255)
	}

MedType::=INTEGER{
	unknown	(0),
	any	(1),
	iso21212	(2), -- 2G
	iso21213	(3), -- 3G
	iso21214	(4), -- IR
	iso21215	(5), -- M5
	iso21216	(6), -- MM
	iso25112	(7), -- 802.16e
	iso25113	(8), -- HC-SDMA
	iso29283	(9), -- 802.20
	iso17515	(10), -- LTE
	iso15628	(128), -- DSRC
	can	(254),
	ethernet	(255)
	} (0..255)

MedUseObsTime::=SEQUENCE {
	value	INTEGER(0..1023), -- valid parameter number (10 bits in PER)
	fill	BIT STRING (SIZE(1)) -- set to zero, extends TimeUnit size.
	unit	TimeUnit
	} -- 2 octets in PER

TimeUnit::=INTEGER{
	microseconds	(0),
	milliseconds	(1),
	seconds	(2),
	minutes	(3),
	hours	(4),
	days	(5),
	weeks	(6),
	months	(7),
	years	(8)
	}(0..31) -- 5 bits in PER

Notify::=SEQUENCE (SIZE(0..255)) OF INTEGER(0..255) -- valid parameter number


PeerRXpower::=INTEGER(0..255)

I-Param::=SEQUENCE{
	fill	BIT STRING (SIZE(2)), -- together with CHOICE tag in one octet.
	param	CHOICE{
	errors	[0] Errors,
	mediumParam	[1] MediumParam,
	commProfile	[2] CommProfile,
	properties	[3] Properties,
	manuDeviceID	[4] PrintableString,
	iTS-scuId	[5] ITS-scuId,
	medID	[6] MedID,
	localCIID	[7] EUI64,
	timeoutReg	[8] INTEGER(0..255),
	macAddress	[9] MACaddress,
	macAddrTemp	[10] MACaddress,
	ciClass	[11] CIclass,
	ciaClass	[12] CIaClass,
	ciStatus	[13] CIstatus,
	suspendSup	[14] INTEGER(0..255),
	minSuspPriority	[15] UserPriority,	-- DEFAULT 255
	notify	[16] Notify,
	medType	[17] MedType,
	regInfo	[18] RegInfo,
	connect	[19] Connect,
	simPin	[20] SimPin,
	providerInfo	[21] ProviderInfo,
	minUserPriority	[22] UserPriority,	-- DEFAULT 0
	queueLevel	[23] QueueLevel,
	queueLowTh	[24] QueueValue,
	queueAlarmTh	[25] QueueValue,
	distancePeer	[26] Distance,
	commRangeRef	[27] Distance,
	timeOfLastRecep	[28] GeneralizedTime,	-- 1 µs resolution
	inactTimeLimit	[29] INTEGER(0..65535),	-- milliseconds
	mediumUsage	[30] MediumUsage,
	medUseObsTime	[31] MedUseObsTime,
	peerMAC	[32] MACaddress,
	virtualCIs	[33] VirtualCIs,
	minPrioCrossCI	[34] UserPriority,
	rxSens	[35] INTEGER(0..255),
	txPower	[36] INTEGER(0..255),
	txPowMax	[37] TxPowMax,
	peerRXpower	[38] PeerRXpower,
	dataRate	[39] DataRate,
	dataRateNW	[40] DataRate,
	dataRatesNW	[41] DataRatesNW,
	dataRateNWreq	[42] DataRate,
	directivity	[43] Directivity,
	blockLength	[44] INTEGER(0..65535),
	freeAirTime	[45] INTEGER(0..255),	-- measured in milliseconds
	frameLengthMax	[46] INTEGER(0..255),	-- measured in milliseconds
	kineVectIn	[47] KineVectIn,
	kineVectOut	[48] KineVectOut,
	cost	[49] MediumCost,
	reliability	[50] INTEGER(0..255),
	logicalChannel	[51] LogicalChannels
	}
}

I-ParamNo::=INTEGER{
	errors	(0),
	mediumParam	(1),
	commProfile	(2),
	properties	(3),
	manuDeviceID	(4),
	iTS-scuId	(5),
	medID	(6),
	localCIID	(7),
	timeoutReg	(8),
	macAddress	(9),
	macAddrTemp	(10),
	ciClass	(11),
	ciaClass	(12),
	ciStatus	(13),
	suspendSup	(14),
	minSuspPriority	(15),
	notify	(16),
	medType	(17),
	regInfo	(18),
	connect	(19),
	simPin	(20),
	providerInfo	(21),
	minUserPriority	(22),
	queueLevel	(23),
	queueLowTh	(24),
	queueAlarmTh	(25),
	distancePeer	(26),
	commRangeRef	(27),
	timeOfLastRecep	(28),
	inactTimeLimit	(29),
	mediumUsage	(30),
	medUseObsTime	(31),
	peerMAC	(32),
	virtualCI	(33),
	minPrioCrossCI	(34),
	rxSens	(35),
	txPower	(36),
	txPowMax	(37),
	peerRXpower	(38),
	dataRate	(39),
	dataRateNW	(40),
	dataRatesNW	(41),
	dataRateNWreq	(42),
	directivity	(43),
	blockLength	(44),
	freeAirTime	(45),
	frameLengthMax	(46),
	kineVectIn	(47),
	kineVectOut	(48),
	cost	(49),
	reliability	(50),
	logicalChannel	(51)
	} (0..255)

SimPin::=OCTET STRING

LogicalChannels::=SEQUENCE (SIZE(0..255)) OF LogicalChannelType

Distance::=INTEGER(0..65535)	-- measured in 1/10 m

MedID::=INTEGER(0..255)

Properties::=SEQUENCE (SIZE(0..255)) OF I-Param -- only selected parameters

ProviderInfo::=SEQUENCE{
	provName	OCTET STRING (SIZE(0..255)), -- Name of provider
	apn	OCTET STRING (SIZE(0..255)), -- Name of access point
	username	OCTET STRING (SIZE(0..255)), -- Log-in name of user
	password	OCTET STRING (SIZE(0..255)) -- Password for log-in
	}

QueueLevel::=SEQUENCE{
	priority	UserPriority,
	level	QueueValue
	}

QueueValue::=INTEGER(0..255)

RegInfo::=SEQUENCE{
	status	RegInfoStatus,
	limits	RegulatoryScheme
	}

RegInfoStatus::=INTEGER{
	notApplicable	(0),
	invalid	(1),
	new	(254),
	valid	(255)
	} (0..255)

RegulatoryScheme::=OCTET STRING  (SIZE(0..65535)) -- content depends on access technology

Tta::=INTEGER(0..65535) -- Resolution 0,1°.

UserPriority::=INTEGER(0..255)

VirtualCIs::=SEQUENCE (SIZE(0..65535))OF RemoteCIID

INsapPrimitivesDown::=SEQUENCE{
	fill	BIT STRING (SIZE(5)), -- set to '0'
	primitives	CHOICE{
	inUnitdataRq	IN-UNITDATA-request,
	inDataAckRq	IN-DATA-ACK-request,
	inReplyAckRq	IN-REPLY-ACK-request,
	inReplyUpdateRq	IN-REPLY-UPDATE-request
	}
	}

IN-UNITDATA-request::=SEQUENCE{
	source-addr	LLserviceAddr,
	dest-addr	LLserviceAddr,
	data	INdata,
	priority	UserPriority,
	accessParams	AccessParameters
	}

IN-DATA-ACK-request::=SEQUENCE{
	source-addr	LLserviceAddr,
	dest-addr	LLserviceAddr,
	data	INdata,
	priority	UserPriority,
	serviceClass	MACServiceClass
	}

IN-REPLY-ACK-request::=SEQUENCE{
	source-addr	LLserviceAddr,
	dest-addr	LLserviceAddr,
	data	INdata,
	priority	UserPriority,
	serviceClass	MACServiceClass
	}

IN-REPLY-UPDATE-request::=SEQUENCE{
	source-addr	LLserviceAddr,
	data	INdata
	}


INsapPrimitivesUp::=SEQUENCE{
	fill	BIT STRING (SIZE(5)), -- set to '0'
	primitives	CHOICE{
	inUnitdataInd	IN-UNITDATA-indication,
	inUnitdataStatusInd	IN-UNITDATA-STATUS-indication,
	inDataAckInd	IN-DATA-ACK-indication,
	inDataAckStatusInd	IN-DATA-ACK-STATUS-indication,
	inReplyInd	IN-REPLY-indication,
	inReplyStatusInd	IN-REPLY-STATUS-indication,
	inReplyUpdateStatusInd	IN-REPLY-UPDATE-STATUS-indication
	}
	}

IN-UNITDATA-indication::=SEQUENCE{
	source-addr	LLserviceAddr,
	dest-addr	LLserviceAddr,
	data	INdata,
	priority	UserPriority,
	accessParams	AccessParameters
	}

IN-UNITDATA-STATUS-indication::=SEQUENCE{
	source-addr	LLserviceAddr,
	dest-addr	LLserviceAddr,
	data	INdata,
	priority	UserPriority,
	accessParams	AccessParameters,
	txStatus	INtxStatus
	}

IN-DATA-ACK-indication::=SEQUENCE{
	source-addr	LLserviceAddr,
	dest-addr	LLserviceAddr,
	data	INdata,
	priority	UserPriority,
	serviceClass	MACServiceClass
	}

IN-DATA-ACK-STATUS-indication::=SEQUENCE{
	source-addr	LLserviceAddr,
	dest-addr	LLserviceAddr,
	data	INdata,
	priority	UserPriority,
	serviceClass	MACServiceClass,
	status	INtxStatus
	}

IN-REPLY-indication::=SEQUENCE{
	source-addr	LLserviceAddr,
	dest-addr	LLserviceAddr,
	data	INdata,
	priority	UserPriority,
	serviceClass	MACServiceClass
	}

IN-REPLY-STATUS-indication::=SEQUENCE{
	source-addr	LLserviceAddr,
	status	INtxStatus
	}

IN-REPLY-UPDATE-STATUS-indication::=SEQUENCE{
	source-addr	LLserviceAddr,
	data	INdata,
	priority	UserPriority,
	accessParams	AccessParameters,
	txStatus	INtxStatus
	}

INdata::=OCTET STRING (SIZE(0..65535))

AccessParameters::=OCTET STRING (SIZE(0..65535))

MACServiceClass::=INTEGER{
	macAckNotUsed	(0),
	macAckUsed	(255)
	} (0..255)

INtxStatus::=INTEGER{
	success	(0),
	queueFull	(1),
	timeout	(2),
	unspecFailure	(255)
	} (0..255)

VCIserialNumber::=INTEGER(0..65535)

EUI64::=OCTET STRING (SIZE(8))

LegacyCIID::=SEQUENCE{
	selector1	OneOCTETones,
	iTS-scuId	ITS-scuId,
	selector2	TwoOCTETones,
	medID	MedID,
	vciSerialNumber	VCIserialNumber
	}

RemoteCIID::=EUI64

OneOCTETones::=INTEGER{
	all	(255)
	} (0..255)

TwoOCTETones::=INTEGER{
	all	(65535)
	} (0..65535)

EUI64MAC48::=SEQUENCE{
	oui	MACoui,
	selector2	TwoOCTETones,
	ext	MACext
	}

MACoui::=SEQUENCE{
	uoi1	INTEGER(0..63),
	ulBit	BOOLEAN,
	igBIT	BOOLEAN,
	uoi2	OCTET STRING (SIZE(2))
	}

MACext::=OCTET STRING (SIZE(3))

MACmcID::=SEQUENCE{
	ucgc	INTEGER(0..63),
	mc	INTEGER{all (3)} (0..3),
	serial	OCTET STRING (SIZE(2))
	}


-- Values

version INTEGER(0..255)::= 1 -- insert version value

/*
   The ASN.1 specification has been checked for conformance to the ASN.1
   standards by OSS ASN.1 Syntax Checker, and by OSS ASN-1STEP
*/

END
